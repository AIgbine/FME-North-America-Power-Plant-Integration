FME workspace PowerPlants_NorthAmerica.fmw

Parameters:
- SourceDataset_SHAPEFILE = $(FME_MF_DIR)input\1_MEX\mex_adm_bnd_a_govmex.shp   # Shapefile(s) Esri source 
- SourceDataset_GEOJSON = $(FME_MF_DIR)input\2_USA\*\*.json   # URL ou fichier GeoJSON source 
- FEATURE_TYPES =
- SourceDataset_SHAPEFILE_3 = $(FME_MF_DIR)input\3_CANADA\*\*.shp   # Shapefile(s) Esri source 
- FEATURE_TYPES_2 =
- SourceDataset_XLSXR_3 = $(FME_MF_DIR)input\2_USA\us-matches.xlsx   # Fichier(s) source Microsoft Excel 
- SourceDataset_XLSXR = $(FME_MF_DIR)input\2_USA\us-matches.xlsx   # Fichier(s) source Microsoft Excel 
- SourceDataset_CSV2 = $(FME_MF_DIR)input\PowerPlantsGE_NorthAmerica.csv   # Fichier(s) source CSV (Comma Separated Value) 
- PARAMETER_2 =   # DestDataset_SHAPEFILE DATA
- DestDataset_SHAPEFILE = $(FME_MF_DIR)output   # Choose a location on your computer
- SourceDataset_SHAPEFILE_5 = $(FME_MF_DIR)input\3_CANADA\*\*.shp   # Shapefile(s) Esri source 
- FEATURE_TYPES_3 =
- SourceDataset_GEOJSON_3 = $(FME_MF_DIR)input\2_USA\*\*.json   # URL ou fichier GeoJSON source 
- FEATURE_TYPES_4 =

Readers:
- SHAPEFILE_1: SHAPEFILE from $(SourceDataset_SHAPEFILE)
- GEOJSON_1: GEOJSON from $(SourceDataset_GEOJSON)
- SHAPEFILE_2: SHAPEFILE from $(SourceDataset_SHAPEFILE_3)
- XLSXR_1: XLSXR from $(SourceDataset_XLSXR)
- XLSXR_2: XLSXR from $(SourceDataset_XLSXR_3)
- CSV2_1: CSV2 from $(SourceDataset_CSV2) in EPSG:4326
- SHAPEFILE_4: SHAPEFILE from $(SourceDataset_SHAPEFILE_5)
- GEOJSON_2: GEOJSON from $(SourceDataset_GEOJSON_3)

Writers:
- SHAPEFILE_3: SHAPEFILE to $(DestDataset_SHAPEFILE) in EPSG:2154

StringSearcher_4
    CASE = no
    MATCHED_RESULT_ATTR = state_code
    REGEXP = \d+
    STRING_TO_SEARCH = @Value(fme_feature_type)
    MATCHED -> AttributeSplitter_3
AttributeSplitter_3
    ATTR_NAME = fme_dataset
    DELIMITER = \
    DROP_EMPTY_PARTS = NO
    LIST_NAME = state_name
    TRIM_TYPE = BOTH
    -> ListIndexer_2
ListIndexer_2
    INDEX = -2
    LIST_ATTR = state_name{}
    -> StringSearcher_5
StringSearcher_5
    CASE = no
    MATCHED_RESULT_ATTR = state_code
    REGEXP = \d+
    STRING_TO_SEARCH = @Value(state_name)
    MATCHED -> StringReplacer_2
StringReplacer_2
    CASE = NO
    FIND_TEXT = \d+
    NO_MATCH = _FME_NO_OP_
    REGEXP = YES
    SRC_ATTRS = state_name
    -> AttributeSplitter_4
AttributeSplitter_4
    ATTR_NAME = fme_feature_type
    DELIMITER = _
    DROP_EMPTY_PARTS = NO
    LIST_NAME = county
    TRIM_TYPE = BOTH
    -> ListIndexer_3
ListIndexer_3
    INDEX = 0
    LIST_ATTR = county{}
    SUFFIX = _code
    -> ListIndexer_4
ListIndexer_4
    INDEX = 1
    LIST_ATTR = county{}
    SUFFIX = _name
    -> SubstringExtractor_4
SubstringExtractor_4
    END = -1
    RESULT_ATTR = county_code_bis
    SRC_STRING = @Value(county_code)
    START = -3
    -> AttributeManager_2
AttributeManager_2
    ATTR_TABLE:
      REMOVE CD_NAME (varchar(50))
      REMOVE PR_ABR (varchar(50))
      REMOVE fme_feature_type (varchar(50))
      REMOVE fme_dataset (varchar(50))
      REMOVE state_name{} (varchar(200))
      REMOVE county{} (varchar(200))
      RENAME_SET_VALUE county_code > county_fips (varchar(200))
      RENAME_SET_VALUE county_code_bis > county_code (buffer)
      SET_TO country (varchar(6)) = CANADA
      SET_TO c_abbr (varchar(2)) = CA
    USER_EXPOSED_ATTRIBUTES = country,c_abbr
    -> Reprojector_2
Reprojector_2
    DEST = EPSG:4326
    INTERPOLATION_TYPE_NAME = Nearest Neighbor
    RASTER_CELL_SIZE = Preserve Cells
    RASTER_TOLERANCE = 0.0
    REPROJECTED -> AttributeManager_5
StringSearcher
    CASE = no
    MATCHED_RESULT_ATTR = state_code
    REGEXP = \d+
    STRING_TO_SEARCH = @Value(ADM1)
    MATCHED -> StringSearcher_2
StringSearcher_2
    CASE = no
    MATCHED_RESULT_ATTR = state_name
    REGEXP = \D+
    STRING_TO_SEARCH = @Value(ADM1)
    MATCHED -> SubstringExtractor
SubstringExtractor
    END = -1
    RESULT_ATTR = county_code
    SRC_STRING = @Value(ADM2)
    START = -3
    -> StringSearcher_3
StringSearcher_3
    CASE = no
    MATCHED_RESULT_ATTR = county_name
    REGEXP = \D+
    STRING_TO_SEARCH = @Value(ADM2)
    MATCHED -> AttributeManager_3
AttributeManager_3
    ATTR_TABLE:
      REMOVE ADM0 (varchar(50))
      REMOVE ADM1 (varchar(50))
      REMOVE ADM2 (varchar(50))
      SET_TO county_fips (varchar(200)) = @Value(state_code)@Value(county_code)
      SET_TO country (varchar(6)) = MEXICO
      SET_TO c_abbr (varchar(2)) = MX
    USER_EXPOSED_ATTRIBUTES = county_fips,country,c,c_abbr
    -> AttributeManager_5
AttributeSplitter_2
    ATTR_NAME = fme_dataset
    DELIMITER = \
    DROP_EMPTY_PARTS = NO
    LIST_NAME = state_abr
    TRIM_TYPE = BOTH
    -> ListIndexer
ListIndexer
    INDEX = -2
    LIST_ATTR = state_abr{}
    -> FeatureMerger [REQUESTOR]
FeatureMerger
    ATTR_ACCUM_MODE = Merge Supplier
    ATTR_CONFLICT_RES = Use Requestor
    IGNORE_NULLS = No
    JOIN_KEYS = @Value(state_abr) @Value(state_abr) AUTO
    MERGE_TYPE = Attributes Only
    PROCESS_DUPS = NO
    REJECT_NULL_MISSING_KEYS = No
    SUPPLIERS_FIRST = No
    MERGED -> AttributeCreator
AttributeCreator
    ATTR_TABLE = SET_TO county_fips (varchar(200)) = @Value(state_fips)@Value(county_nb)
    -> FeatureMerger_2 [REQUESTOR]
SubstringExtractor_2
    END = -1
    RESULT_ATTR = county_code
    SRC_STRING = @Value(county_fips)
    START = -3
    -> SubstringExtractor_3
SubstringExtractor_3
    END = 1
    RESULT_ATTR = state_code
    SRC_STRING = @Value(county_fips)
    START = 0
    -> StringReplacer
StringReplacer
    CASE = NO
    FIND_TEXT = " county"
    NO_MATCH = _FME_NO_OP_
    REGEXP = NO
    SRC_ATTRS = county_name
    -> FeatureMerger_2 [SUPPLIER]
FeatureMerger_2
    ATTR_ACCUM_MODE = Merge Supplier
    ATTR_CONFLICT_RES = Use Requestor
    IGNORE_NULLS = No
    JOIN_KEYS = @Value(county_fips) @Value(county_fips) AUTO
    MERGE_TYPE = Attributes Only
    PROCESS_DUPS = NO
    REJECT_NULL_MISSING_KEYS = No
    SUPPLIERS_FIRST = No
    MERGED -> AttributeManager
AttributeManager
    ATTR_TABLE:
      REMOVE county_nb (buffer)
      REMOVE fme_feature_type (buffer)
      REMOVE fme_dataset (buffer)
      REMOVE state_abr{} (varchar(200))
      REMOVE state_abr (varchar(200))
      REMOVE state_fips (number(2,0))
      SET_TO country (varchar(3)) = USA
      SET_TO c_abbr (varchar(2)) = US
    USER_EXPOSED_ATTRIBUTES = country,c_abbr
    -> AttributeManager_5
AttributeManager_5
    -> Reprojector_3
Reprojector_3
    DEST = EPSG:4326
    INTERPOLATION_TYPE_NAME = Nearest Neighbor
    RASTER_CELL_SIZE = Preserve Cells
    RASTER_TOLERANCE = 0.0
    REPROJECTED -> SpatialFilter [Filter]
CSV (reader CSV2_1)
    attributes: Latitude varchar(32), Longitude varchar(33), Facility varchar(73), Owner varchar(118), Operator varchar(100), PrimSource varchar(14), Coal_MW real32, NG_MW real32, Petrol_MW real32, Other_MW real32, Hydro_MW real32, PS_MW real32, Nuclear_MW real32, Solar_MW real32, Wind_MW real32, Geo_MW real32, Bio_MW real32, Tidal_MW uint32
    -> StringReplacer_3
AttributeManager_4
    ATTR_TABLE = SET_TO pp_type (varchar(200)) = FME_CONDITIONAL:DEFAULT_VALUE'Both'BOOL_OP;OR;COMPOSITE_TEST;1 OR 2 OR 3 OR 4 OR 5 OR 6;TEST @Value(PrimSource) = Biomass;TEST @Value(PrimSource) = Geothermal;TEST @Value(PrimSource) = Hydroelectric;TEST @Value(PrimSource) = Solar;TEST @Value(PrimSource) = Tidal;TEST @Value(PrimSource) = Wind'Renewable'BOOL_OP;OR;COMPOSITE_TEST;1 OR 2 OR 3 OR 4;TEST @Value(PrimSource) = Coal;TEST @Value(PrimSource) = Natural Gas;TEST @Value(PrimSource) = Nuclear;TEST @Value(PrimSource) = Petroleum'Non renewable'FME_NUM_CONDITIONS3___
    USER_EXPOSED_ATTRIBUTES = pp_type
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeManager_6
AttributeManager_6
    ATTR_TABLE = SET_TO total_mw (real64) = @Evaluate(@Value(Bio_MW)+@Value(Coal_MW)+@Value(Geo_MW)+@Value(Hydro_MW)+@Value(NG_MW)+@Value(Nuclear_MW)+@Value(Other_MW)+@Value(Petrol_MW)+@Value(PS_MW)+@Value(Solar_MW)+@Value(Tidal_MW)+@Value(Wind_MW))
    USER_EXPOSED_ATTRIBUTES = total_mw
    -> TOWN_COMPLETE (writer SHAPEFILE_3)
Note: Getting an attribute value in the file name will generate as many files as unique values in the attribute
TOWN_COMPLETE (writer SHAPEFILE_3)
    attributes: state_name varchar(24), county_fip varchar(200), county_nam varchar(28), county_cod varchar(254), state_code varchar(254), country varchar(3), c_abbr varchar(2), Latitude varchar(32), Longitude varchar(33), Facility varchar(73), Owner varchar(118), Operator varchar(100), PrimSource varchar(14), Coal_MW float, NG_MW float, Petrol_MW float, Other_MW float, Hydro_MW float, PS_MW float, Nuclear_MW float, Solar_MW float, Wind_MW float, Geo_MW float, Bio_MW float, Tidal_MW double, Q__list_la varchar(200), Q__list_lo varchar(200), lat double, long double, pp_type varchar(200),
      Q__predica varchar(254), total_mw double
StringReplacer_5
    CASE = NO
    FIND_TEXT = (\s+-\s+|\s+)
    NO_MATCH = _FME_NO_OP_
    REGEXP = YES
    REPLACE_TEXT = FME_CONDITIONAL:DEFAULT_VALUE''BOOL_OP;OR;COMPOSITE_TEST;1;CASE_SENSITIVE_TEST @Value(name) CONTAINS_REGEX \s+-\s+'-'BOOL_OP;OR;COMPOSITE_TEST;1;CASE_SENSITIVE_TEST @Value(name) CONTAINS_REGEX \s+' 'FME_NUM_CONDITIONS3___
    SRC_ATTRS = name
StringReplacer_4
    CASE = NO
    FIND_TEXT = (\$\s+|\s+\*)
    NO_MATCH = _FME_NO_OP_
    REGEXP = YES
    SRC_ATTRS = name
Reprojector
    DEST = EPSG:2154
    INTERPOLATION_TYPE_NAME = Nearest Neighbor
    RASTER_CELL_SIZE = Preserve Cells
    RASTER_TOLERANCE = 0.0
    SOURCE = EPSG:4326

Bookmark: CANADA
48001_Division No. 1 (reader SHAPEFILE_2)
    attributes: CD_NAME varchar(50), PR_ABR varchar(50)
48001_Division No. 1 (reader SHAPEFILE_4)
    attributes: CD_NAME varchar(50), PR_ABR varchar(50)
    -> StringSearcher_4

Bookmark: MEXICO
mex_adm_bnd_a_govmex (reader SHAPEFILE_1)
    attributes: ADM0 varchar(50), ADM1 varchar(50), ADM2 varchar(50)
    -> StringSearcher

Bookmark: USA
us-county-boundaries (reader GEOJSON_1)
    attributes: county_nb string
us-county-boundaries (reader GEOJSON_2)
    attributes: county_nb string
    -> AttributeSplitter_2
us-states-matches (reader XLSXR_1)
    attributes: state_fips number(2,0), state_abr char(2), state_name char(24)
    -> FeatureMerger [SUPPLIER]
us-county-matches (reader XLSXR_2)
    attributes: county_fips number(5,0), county_name char(28)
    -> SubstringExtractor_2

Bookmark: EXERCISE 8 - LISTS AND REGEX
StringReplacer_3
    CASE = NO
    FIND_TEXT = [°'"]
    NO_MATCH = _FME_NO_OP_
    REGEXP = YES
    REPLACE_TEXT = " "
    SRC_ATTRS = Latitude,Longitude
    -> AttributeSplitter
AttributeSplitter
    ATTR_NAME = Latitude
    DELIMITER = " "
    DROP_EMPTY_PARTS = NO
    LIST_NAME = _list_lat
    TRIM_TYPE = BOTH
    -> AttributeSplitter_5
AttributeSplitter_5
    ATTR_NAME = Longitude
    DELIMITER = " "
    DROP_EMPTY_PARTS = NO
    LIST_NAME = _list_long
    TRIM_TYPE = BOTH
    -> DecimalDegreesCalculator
DecimalDegreesCalculator
    DEGREES = _list_lat{0}
    DEST_ATTR = lat
    MINUTES = _list_lat{1}
    SECONDS = _list_lat{2}
    -> DecimalDegreesCalculator_2
DecimalDegreesCalculator_2
    DEGREES = _list_long{0}
    DEST_ATTR = long
    MINUTES = _list_long{1}
    SECONDS = _list_long{2}
    -> VertexCreator
VertexCreator
    MEASURE_TYPE = Continuous
    MODE_NAME = Replace with Point
    XVAL = @Value(long)
    YVAL = @Value(lat)
    -> AttributeManager_4
